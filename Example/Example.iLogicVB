'This file has been auto-generated by Ilogic Collector - version 1
'Collection timestamp: 2020/01/16 - 19:49
'https://github.com/jordanrobot/iLogicCollector

'
'</iLogicCollectorHeader>

AddReference "Company.Library1.dll"
AddReference "microsoft.office.interop.excel.dll"
Imports Inventor
Imports System.IO
Imports Microsoft.Office.Interop
Imports System.Runtime.InteropServices
Imports Company.Library1
Imports System.Text.RegularExpressions


'Module Main '</iLogicCollectorHide>

    Public Sub Main()

        Dim oSphere As New SphereClass.New(24, 0, 0, 0)
        Dim oExporter As New ExporterClass


        If oSphere.Volume < 360 Then

            oExporter.ToSat(oSphere, output_file)

        End If

    End Sub

    Public Enum ShapeTypeEnum
        Sphere = 0
        Box
        Torus
    End Enum

'End Module '</iLogicCollectorHide>


Public Class SphereClass

    Public Property Diameter As Double
    Public Property Center As New Blah.Blah.Point3D
    Public Property Diameter As Double


    Public Sub New(diam As Double, x As Double, y As Double, z As Double)
        Diameter = diam
        Center.Add = (x, y, z)
    End Sub

    Public Function Volume()
        Returns(Math.Pi * (4 / 3) * (Diameter / 2) ^ 3)
    End Function

    Public Function SurfaceArea()
        Returns(Math.Pi * 2 * Diameter ^ 2)
    End Function

End Class


Public Class ExporterClass

    Public Sub New()

    End Sub

    Public Function ToSat(file As String)
        'Code to implement SAT file export
    End Function

    Public Function ToStep(file As String)
        'Code to implement STEP file export
    End Function

End Class
